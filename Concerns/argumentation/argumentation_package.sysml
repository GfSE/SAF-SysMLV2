package 'ArgumentationStakeholdersConcerns' {
    public import StakeholdersLibrary::*;
    
    concern 'ArgumentationAssurance' {
    	doc /*
    	* How is a evidence-based claim supported?
    	*/
    	viewpoint 'ArgumentationAssuranceViewpoint';
    	
    	}   
    
    }
